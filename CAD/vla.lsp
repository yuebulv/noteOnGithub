(defun c:ch6()
	(vl-load-com)
	(setq acadobj(vlax-get-acad-object))
	(setq dwgobj(vla-get-ActiveDocument acadobj))
	(setq mspace(vla-get-ModelSpace dwgobj))
	;绘制二阶楼梯练习(100*80)
	(setq p1(getpoint"左下角基准点："))
	(setq p2 (polar p1 0 100) p3 (polar p2 (/ pi 2) 40)
		p4 (polar p3 pi 50) p5 (polar p4 (/ pi 2)40)
		p6 (polar p5 pi 50)
	)
	(vla-addline mspace (vlax-3d-point p1)(vlax-3d-point p2))
	(vla-addline mspace(vlax-3d-point p2)(vlax-3d-point p3))
	(vla-addline mspace(vlax-3d-point p3)(vlax-3d-point p4))
	(vla-addline mspace(vlax-3d-point p4)(vlax-3d-point p5))
	(vla-addline mspace(vlax-3d-point p5)(vlax-3d-point p6))
	(vla-addline mspace(vlax-3d-point p1)(vlax-3d-point p6))
	;为阶梯加上两个同心圆
	(setq rr (/ (distance p1 p4) 2))
	(vla-addcircle mspace (vlax-3d-point p1) rr)
	(vla-addcircle mspace (vlax-3d-point p1)(/ rr 2))
       	;为阶梯加上两组尺寸标注
	(setq pa (vlax-3d-point(polar p6 (/ pi 2) 10)))
	(vla-adddimrotated mspace (vlax-3d-point p6) (vlax-3d-point p3) pa 0)
	(setq pb (vlax-3d-point (polar p2 0 10)))
	(vla-adddimrotated mspace (vlax-3d-point p2)(vlax-3d-point p5)pb(/ pi 2))
	      
)
